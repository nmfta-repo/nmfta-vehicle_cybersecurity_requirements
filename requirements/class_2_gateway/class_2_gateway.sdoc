[DOCUMENT]
TITLE: Class 2 Vehicle Gateway Security Requirements

[GRAMMAR]
IMPORT_FROM_FILE: @vcr_grammar

[TEXT]
STATEMENT: >>>
This document specifies cybersecurity requirements for Class 2 vehicle components: **Vehicle Gateway**.

Class 2 devices are truck modules intended to perform gateway functions (transport, translate, transform, filter, or encapsulate data) between two or more vehicle network segments.

Examples include:
- Onboard Diagnostics Connector Gateway (Central Gateway / CGW) (J1939 SA 39, 17, 44, 49, 50, 77)
- 3rd Party Equipment Gateway (J1939 SA 249)
- Telematics Interface Gateway
<<<

[[SECTION]]
TITLE: Baseline Security Requirements Applicability

[REQUIREMENT]
UID: C2-AA-010
STATUS: Draft
TAGS: NEEDS_WORKING_GROUP_REVIEW
STATEMENT: >>>
Class 2 devices SHALL satisfy baseline requirement AA-010.
<<<
RELATIONS:
- TYPE: Parent
  VALUE: AA-010
  ROLE: Refines

[REQUIREMENT]
UID: C2-AC-010
STATUS: Draft
TAGS: NEEDS_WORKING_GROUP_REVIEW
STATEMENT: >>>
Class 2 devices SHALL satisfy baseline requirement AC-010.
<<<
RELATIONS:
- TYPE: Parent
  VALUE: AC-010
  ROLE: Refines

[REQUIREMENT]
UID: C2-AC-020
STATUS: Draft
TAGS: NEEDS_WORKING_GROUP_REVIEW
STATEMENT: >>>
Class 2 devices SHALL satisfy baseline requirement AC-020.
<<<
RELATIONS:
- TYPE: Parent
  VALUE: AC-020
  ROLE: Refines

[REQUIREMENT]
UID: C2-AC-030
STATUS: Draft
TAGS: NEEDS_WORKING_GROUP_REVIEW
STATEMENT: >>>
Class 2 devices SHALL satisfy baseline requirement AC-030.
<<<
RELATIONS:
- TYPE: Parent
  VALUE: AC-030
  ROLE: Refines

[REQUIREMENT]
UID: C2-AC-040
STATUS: Draft
TAGS: NEEDS_WORKING_GROUP_REVIEW
STATEMENT: >>>
Class 2 devices SHALL satisfy baseline requirement AC-040.
<<<
RELATIONS:
- TYPE: Parent
  VALUE: AC-040
  ROLE: Refines

[REQUIREMENT]
UID: C2-AC-041
STATUS: Draft
TAGS: NEEDS_WORKING_GROUP_REVIEW
STATEMENT: >>>
Class 2 devices SHALL satisfy baseline requirement AC-041.
<<<
RELATIONS:
- TYPE: Parent
  VALUE: AC-041
  ROLE: Refines

[REQUIREMENT]
UID: C2-AC-050
STATUS: Draft
TAGS: NEEDS_WORKING_GROUP_REVIEW
STATEMENT: >>>
Class 2 devices SHALL satisfy baseline requirement AC-050.
<<<
RELATIONS:
- TYPE: Parent
  VALUE: AC-050
  ROLE: Refines

[REQUIREMENT]
UID: C2-AC-070
STATUS: Draft
TAGS: NEEDS_WORKING_GROUP_REVIEW
STATEMENT: >>>
Class 2 devices SHALL satisfy baseline requirement AC-070.
<<<
RELATIONS:
- TYPE: Parent
  VALUE: AC-070
  ROLE: Refines

[REQUIREMENT]
UID: C2-AC-080
STATUS: Draft
TAGS: NEEDS_WORKING_GROUP_REVIEW
STATEMENT: >>>
Class 2 devices SHALL satisfy baseline requirement AC-080.
<<<
RELATIONS:
- TYPE: Parent
  VALUE: AC-080
  ROLE: Refines

[REQUIREMENT]
UID: C2-CM-010
STATUS: Draft
TAGS: NEEDS_WORKING_GROUP_REVIEW
STATEMENT: >>>
Class 2 devices SHALL satisfy baseline requirement CM-010.
<<<
RELATIONS:
- TYPE: Parent
  VALUE: CM-010
  ROLE: Refines

[REQUIREMENT]
UID: C2-CM-020
STATUS: Draft
TAGS: NEEDS_WORKING_GROUP_REVIEW
STATEMENT: >>>
Class 2 devices SHALL satisfy baseline requirement CM-020.
<<<
RELATIONS:
- TYPE: Parent
  VALUE: CM-020
  ROLE: Refines

[REQUIREMENT]
UID: C2-CM-030
STATUS: Draft
TAGS: NEEDS_WORKING_GROUP_REVIEW
STATEMENT: >>>
Class 2 devices SHALL satisfy baseline requirement CM-030.
<<<
RELATIONS:
- TYPE: Parent
  VALUE: CM-030
  ROLE: Refines

[REQUIREMENT]
UID: C2-CM-040
STATUS: Draft
TAGS: NEEDS_WORKING_GROUP_REVIEW
STATEMENT: >>>
Class 2 devices SHALL satisfy baseline requirement CM-040.
<<<
RELATIONS:
- TYPE: Parent
  VALUE: CM-040
  ROLE: Refines

[REQUIREMENT]
UID: C2-IA-010
STATUS: Draft
TAGS: NEEDS_WORKING_GROUP_REVIEW
STATEMENT: >>>
Class 2 devices SHALL satisfy baseline requirement IA-010.
<<<
RELATIONS:
- TYPE: Parent
  VALUE: IA-010
  ROLE: Refines

[REQUIREMENT]
UID: C2-IA-020
STATUS: Draft
TAGS: NEEDS_WORKING_GROUP_REVIEW
STATEMENT: >>>
Class 2 devices SHALL satisfy baseline requirement IA-020.
<<<
RELATIONS:
- TYPE: Parent
  VALUE: IA-020
  ROLE: Refines

[REQUIREMENT]
UID: C2-IA-030
STATUS: Draft
TAGS: NEEDS_WORKING_GROUP_REVIEW
STATEMENT: >>>
Class 2 devices SHALL satisfy baseline requirement IA-030.
<<<
RELATIONS:
- TYPE: Parent
  VALUE: IA-030
  ROLE: Refines

[REQUIREMENT]
UID: C2-IR-010
STATUS: Draft
TAGS: NEEDS_WORKING_GROUP_REVIEW
STATEMENT: >>>
Class 2 devices SHALL satisfy baseline requirement IR-010.
<<<
RELATIONS:
- TYPE: Parent
  VALUE: IR-010
  ROLE: Refines

[REQUIREMENT]
UID: C2-M-010
STATUS: Draft
TAGS: NEEDS_WORKING_GROUP_REVIEW
STATEMENT: >>>
Class 2 devices SHALL satisfy baseline requirement M-010.
<<<
RELATIONS:
- TYPE: Parent
  VALUE: M-010
  ROLE: Refines

[REQUIREMENT]
UID: C2-M-020
STATUS: Draft
TAGS: NEEDS_WORKING_GROUP_REVIEW
STATEMENT: >>>
Class 2 devices SHALL satisfy baseline requirement M-020.
<<<
RELATIONS:
- TYPE: Parent
  VALUE: M-020
  ROLE: Refines

[REQUIREMENT]
UID: C2-M-030
STATUS: Draft
TAGS: NEEDS_WORKING_GROUP_REVIEW
STATEMENT: >>>
Class 2 devices SHALL satisfy baseline requirement M-030.
<<<
RELATIONS:
- TYPE: Parent
  VALUE: M-030
  ROLE: Refines

[REQUIREMENT]
UID: C2-M-031
STATUS: Draft
TAGS: NEEDS_WORKING_GROUP_REVIEW
STATEMENT: >>>
Class 2 devices SHALL satisfy baseline requirement M-031.
<<<
RELATIONS:
- TYPE: Parent
  VALUE: M-031
  ROLE: Refines

[REQUIREMENT]
UID: C2-M-032
STATUS: Draft
TAGS: NEEDS_WORKING_GROUP_REVIEW
STATEMENT: >>>
Class 2 devices SHALL satisfy baseline requirement M-032.
<<<
RELATIONS:
- TYPE: Parent
  VALUE: M-032
  ROLE: Refines

[REQUIREMENT]
UID: C2-M-040
STATUS: Draft
TAGS: NEEDS_WORKING_GROUP_REVIEW
STATEMENT: >>>
Class 2 devices SHALL satisfy baseline requirement M-040.
<<<
RELATIONS:
- TYPE: Parent
  VALUE: M-040
  ROLE: Refines

[REQUIREMENT]
UID: C2-P-010
STATUS: Draft
TAGS: NEEDS_WORKING_GROUP_REVIEW
STATEMENT: >>>
Class 2 devices SHALL satisfy baseline requirement P-010.
<<<
RELATIONS:
- TYPE: Parent
  VALUE: P-010
  ROLE: Refines

[REQUIREMENT]
UID: C2-P-020
STATUS: Draft
TAGS: NEEDS_WORKING_GROUP_REVIEW
STATEMENT: >>>
Class 2 devices SHALL satisfy baseline requirement P-020.
<<<
RELATIONS:
- TYPE: Parent
  VALUE: P-020
  ROLE: Refines

[REQUIREMENT]
UID: C2-PS-010
STATUS: Draft
TAGS: NEEDS_WORKING_GROUP_REVIEW
STATEMENT: >>>
Class 2 devices SHALL satisfy baseline requirement PS-010.
<<<
RELATIONS:
- TYPE: Parent
  VALUE: PS-010
  ROLE: Refines

[REQUIREMENT]
UID: C2-RA-010
STATUS: Draft
TAGS: NEEDS_WORKING_GROUP_REVIEW
STATEMENT: >>>
Class 2 devices SHALL satisfy baseline requirement RA-010.
<<<
RELATIONS:
- TYPE: Parent
  VALUE: RA-010
  ROLE: Refines

[REQUIREMENT]
UID: C2-RA-020
STATUS: Draft
TAGS: NEEDS_WORKING_GROUP_REVIEW
STATEMENT: >>>
Class 2 devices SHALL satisfy baseline requirement RA-020.
<<<
RELATIONS:
- TYPE: Parent
  VALUE: RA-020
  ROLE: Refines

[REQUIREMENT]
UID: C2-SAA-010
STATUS: Draft
TAGS: NEEDS_WORKING_GROUP_REVIEW
STATEMENT: >>>
Class 2 devices SHALL satisfy baseline requirement SAA-010.
<<<
RELATIONS:
- TYPE: Parent
  VALUE: SAA-010
  ROLE: Refines

[REQUIREMENT]
UID: C2-SAA-020
STATUS: Draft
TAGS: NEEDS_WORKING_GROUP_REVIEW
STATEMENT: >>>
Class 2 devices SHALL satisfy baseline requirement SAA-020.
<<<
RELATIONS:
- TYPE: Parent
  VALUE: SAA-020
  ROLE: Refines

[REQUIREMENT]
UID: C2-SAA-030
STATUS: Draft
TAGS: NEEDS_WORKING_GROUP_REVIEW
STATEMENT: >>>
Class 2 devices SHALL satisfy baseline requirement SAA-030.
<<<
RELATIONS:
- TYPE: Parent
  VALUE: SAA-030
  ROLE: Refines

[REQUIREMENT]
UID: C2-SAA-040
STATUS: Draft
TAGS: NEEDS_WORKING_GROUP_REVIEW
STATEMENT: >>>
Class 2 devices SHALL satisfy baseline requirement SAA-040.
<<<
RELATIONS:
- TYPE: Parent
  VALUE: SAA-040
  ROLE: Refines

[REQUIREMENT]
UID: C2-SAA-050
STATUS: Draft
TAGS: NEEDS_WORKING_GROUP_REVIEW
STATEMENT: >>>
Class 2 devices SHALL satisfy baseline requirement SAA-050.
<<<
RELATIONS:
- TYPE: Parent
  VALUE: SAA-050
  ROLE: Refines

[REQUIREMENT]
UID: C2-SCP-010
STATUS: Draft
TAGS: NEEDS_WORKING_GROUP_REVIEW
STATEMENT: >>>
Class 2 devices SHALL satisfy baseline requirement SCP-010.
<<<
RELATIONS:
- TYPE: Parent
  VALUE: SCP-010
  ROLE: Refines

[REQUIREMENT]
UID: C2-SCP-011
STATUS: Draft
TAGS: NEEDS_WORKING_GROUP_REVIEW
STATEMENT: >>>
Class 2 devices SHALL satisfy baseline requirement SCP-011.
<<<
RELATIONS:
- TYPE: Parent
  VALUE: SCP-011
  ROLE: Refines

[REQUIREMENT]
UID: C2-SCP-020
STATUS: Draft
TAGS: NEEDS_WORKING_GROUP_REVIEW
STATEMENT: >>>
Class 2 devices SHALL satisfy baseline requirement SCP-020.
<<<
RELATIONS:
- TYPE: Parent
  VALUE: SCP-020
  ROLE: Refines

[REQUIREMENT]
UID: C2-SCP-030
STATUS: Draft
TAGS: NEEDS_WORKING_GROUP_REVIEW
STATEMENT: >>>
Class 2 devices SHALL satisfy baseline requirement SCP-030.
<<<
RELATIONS:
- TYPE: Parent
  VALUE: SCP-030
  ROLE: Refines

[REQUIREMENT]
UID: C2-SCP-040
STATUS: Draft
TAGS: NEEDS_WORKING_GROUP_REVIEW
STATEMENT: >>>
Class 2 devices SHALL satisfy baseline requirement SCP-040.
<<<
RELATIONS:
- TYPE: Parent
  VALUE: SCP-040
  ROLE: Refines

[REQUIREMENT]
UID: C2-SCP-060
STATUS: Draft
TAGS: NEEDS_WORKING_GROUP_REVIEW
STATEMENT: >>>
Class 2 devices SHALL satisfy baseline requirement SCP-060.
<<<
RELATIONS:
- TYPE: Parent
  VALUE: SCP-060
  ROLE: Refines

[REQUIREMENT]
UID: C2-SCP-090
STATUS: Draft
TAGS: NEEDS_WORKING_GROUP_REVIEW
STATEMENT: >>>
Class 2 devices SHALL satisfy baseline requirement SCP-090.
<<<
RELATIONS:
- TYPE: Parent
  VALUE: SCP-090
  ROLE: Refines

[REQUIREMENT]
UID: C2-SCP-091
STATUS: Draft
TAGS: NEEDS_WORKING_GROUP_REVIEW
STATEMENT: >>>
Class 2 devices SHALL satisfy baseline requirement SCP-091.
<<<
RELATIONS:
- TYPE: Parent
  VALUE: SCP-091
  ROLE: Refines

[REQUIREMENT]
UID: C2-SCP-092
STATUS: Draft
TAGS: NEEDS_WORKING_GROUP_REVIEW
STATEMENT: >>>
Class 2 devices SHALL satisfy baseline requirement SCP-092.
<<<
RELATIONS:
- TYPE: Parent
  VALUE: SCP-092
  ROLE: Refines

[REQUIREMENT]
UID: C2-SCP-100
STATUS: Draft
TAGS: NEEDS_WORKING_GROUP_REVIEW
STATEMENT: >>>
Class 2 devices SHALL satisfy baseline requirement SCP-100.
<<<
RELATIONS:
- TYPE: Parent
  VALUE: SCP-100
  ROLE: Refines

[REQUIREMENT]
UID: C2-SCP-110
STATUS: Draft
TAGS: NEEDS_WORKING_GROUP_REVIEW
STATEMENT: >>>
Class 2 devices SHALL satisfy baseline requirement SCP-110.
<<<
RELATIONS:
- TYPE: Parent
  VALUE: SCP-110
  ROLE: Refines

[REQUIREMENT]
UID: C2-SCP-120
STATUS: Draft
TAGS: NEEDS_WORKING_GROUP_REVIEW
STATEMENT: >>>
Class 2 devices SHALL satisfy baseline requirement SCP-120.
<<<
RELATIONS:
- TYPE: Parent
  VALUE: SCP-120
  ROLE: Refines

[REQUIREMENT]
UID: C2-SCP-130
STATUS: Draft
TAGS: NEEDS_WORKING_GROUP_REVIEW
STATEMENT: >>>
Class 2 devices SHALL satisfy baseline requirement SCP-130.
<<<
RELATIONS:
- TYPE: Parent
  VALUE: SCP-130
  ROLE: Refines

[REQUIREMENT]
UID: C2-SCP-140
STATUS: Draft
TAGS: NEEDS_WORKING_GROUP_REVIEW
STATEMENT: >>>
Class 2 devices SHALL satisfy baseline requirement SCP-140.
<<<
RELATIONS:
- TYPE: Parent
  VALUE: SCP-140
  ROLE: Refines

[REQUIREMENT]
UID: C2-SII-010
STATUS: Draft
TAGS: NEEDS_WORKING_GROUP_REVIEW
STATEMENT: >>>
Class 2 devices SHALL satisfy baseline requirement SII-010.
<<<
RELATIONS:
- TYPE: Parent
  VALUE: SII-010
  ROLE: Refines

[REQUIREMENT]
UID: C2-SII-011
STATUS: Draft
TAGS: NEEDS_WORKING_GROUP_REVIEW
STATEMENT: >>>
Class 2 devices SHALL satisfy baseline requirement SII-011.
<<<
RELATIONS:
- TYPE: Parent
  VALUE: SII-011
  ROLE: Refines

[REQUIREMENT]
UID: C2-SII-020
STATUS: Draft
TAGS: NEEDS_WORKING_GROUP_REVIEW
STATEMENT: >>>
Class 2 devices SHALL satisfy baseline requirement SII-020.
<<<
RELATIONS:
- TYPE: Parent
  VALUE: SII-020
  ROLE: Refines

[REQUIREMENT]
UID: C2-SII-021
STATUS: Draft
TAGS: NEEDS_WORKING_GROUP_REVIEW
STATEMENT: >>>
Class 2 devices SHALL satisfy baseline requirement SII-021.
<<<
RELATIONS:
- TYPE: Parent
  VALUE: SII-021
  ROLE: Refines

[REQUIREMENT]
UID: C2-SII-030
STATUS: Draft
TAGS: NEEDS_WORKING_GROUP_REVIEW
STATEMENT: >>>
Class 2 devices SHALL satisfy baseline requirement SII-030.
<<<
RELATIONS:
- TYPE: Parent
  VALUE: SII-030
  ROLE: Refines

[REQUIREMENT]
UID: C2-SII-040
STATUS: Draft
TAGS: NEEDS_WORKING_GROUP_REVIEW
STATEMENT: >>>
Class 2 devices SHALL satisfy baseline requirement SII-040.
<<<
RELATIONS:
- TYPE: Parent
  VALUE: SII-040
  ROLE: Refines

[REQUIREMENT]
UID: C2-SII-041
STATUS: Draft
TAGS: NEEDS_WORKING_GROUP_REVIEW
STATEMENT: >>>
Class 2 devices SHALL satisfy baseline requirement SII-041.
<<<
RELATIONS:
- TYPE: Parent
  VALUE: SII-041
  ROLE: Refines

[REQUIREMENT]
UID: C2-SII-060
STATUS: Draft
TAGS: NEEDS_WORKING_GROUP_REVIEW
STATEMENT: >>>
Class 2 devices SHALL satisfy baseline requirement SII-060.
<<<
RELATIONS:
- TYPE: Parent
  VALUE: SII-060
  ROLE: Refines

[REQUIREMENT]
UID: C2-SII-070
STATUS: Draft
TAGS: NEEDS_WORKING_GROUP_REVIEW
STATEMENT: >>>
Class 2 devices SHALL satisfy baseline requirement SII-070.
<<<
RELATIONS:
- TYPE: Parent
  VALUE: SII-070
  ROLE: Refines

[REQUIREMENT]
UID: C2-SII-071
STATUS: Draft
TAGS: NEEDS_WORKING_GROUP_REVIEW
STATEMENT: >>>
Class 2 devices SHALL satisfy baseline requirement SII-071.
<<<
RELATIONS:
- TYPE: Parent
  VALUE: SII-071
  ROLE: Refines

[REQUIREMENT]
UID: C2-SII-080
STATUS: Draft
TAGS: NEEDS_WORKING_GROUP_REVIEW
STATEMENT: >>>
Class 2 devices SHALL satisfy baseline requirement SII-080.
<<<
RELATIONS:
- TYPE: Parent
  VALUE: SII-080
  ROLE: Refines

[REQUIREMENT]
UID: C2-SII-081
STATUS: Draft
TAGS: NEEDS_WORKING_GROUP_REVIEW
STATEMENT: >>>
Class 2 devices SHALL satisfy baseline requirement SII-081.
<<<
RELATIONS:
- TYPE: Parent
  VALUE: SII-081
  ROLE: Refines

[REQUIREMENT]
UID: C2-SII-090
STATUS: Draft
TAGS: NEEDS_WORKING_GROUP_REVIEW
STATEMENT: >>>
Class 2 devices SHALL satisfy baseline requirement SII-090.
<<<
RELATIONS:
- TYPE: Parent
  VALUE: SII-090
  ROLE: Refines

[REQUIREMENT]
UID: C2-SII-100
STATUS: Draft
TAGS: NEEDS_WORKING_GROUP_REVIEW
STATEMENT: >>>
Class 2 devices SHALL satisfy baseline requirement SII-100.
<<<
RELATIONS:
- TYPE: Parent
  VALUE: SII-100
  ROLE: Refines

[REQUIREMENT]
UID: C2-SII-110
STATUS: Draft
TAGS: NEEDS_WORKING_GROUP_REVIEW
STATEMENT: >>>
Class 2 devices SHALL satisfy baseline requirement SII-110.
<<<
RELATIONS:
- TYPE: Parent
  VALUE: SII-110
  ROLE: Refines

[REQUIREMENT]
UID: C2-SII-120
STATUS: Draft
TAGS: NEEDS_WORKING_GROUP_REVIEW
STATEMENT: >>>
Class 2 devices SHALL satisfy baseline requirement SII-120.
<<<
RELATIONS:
- TYPE: Parent
  VALUE: SII-120
  ROLE: Refines

[REQUIREMENT]
UID: C2-SII-130
STATUS: Draft
TAGS: NEEDS_WORKING_GROUP_REVIEW
STATEMENT: >>>
Class 2 devices SHALL satisfy baseline requirement SII-130.
<<<
RELATIONS:
- TYPE: Parent
  VALUE: SII-130
  ROLE: Refines

[REQUIREMENT]
UID: C2-SII-140
STATUS: Draft
TAGS: NEEDS_WORKING_GROUP_REVIEW
STATEMENT: >>>
Class 2 devices SHALL satisfy baseline requirement SII-140.
<<<
RELATIONS:
- TYPE: Parent
  VALUE: SII-140
  ROLE: Refines

[REQUIREMENT]
UID: C2-SII-150
STATUS: Draft
TAGS: NEEDS_WORKING_GROUP_REVIEW
STATEMENT: >>>
Class 2 devices SHALL satisfy baseline requirement SII-150.
<<<
RELATIONS:
- TYPE: Parent
  VALUE: SII-150
  ROLE: Refines

[REQUIREMENT]
UID: C2-SII-170
STATUS: Draft
TAGS: NEEDS_WORKING_GROUP_REVIEW
STATEMENT: >>>
Class 2 devices SHALL satisfy baseline requirement SII-170.
<<<
RELATIONS:
- TYPE: Parent
  VALUE: SII-170
  ROLE: Refines

[REQUIREMENT]
UID: C2-SII-171
STATUS: Draft
TAGS: NEEDS_WORKING_GROUP_REVIEW
STATEMENT: >>>
Class 2 devices SHALL satisfy baseline requirement SII-171.
<<<
RELATIONS:
- TYPE: Parent
  VALUE: SII-171
  ROLE: Refines

[REQUIREMENT]
UID: C2-SII-180
STATUS: Draft
TAGS: NEEDS_WORKING_GROUP_REVIEW
STATEMENT: >>>
Class 2 devices SHALL satisfy baseline requirement SII-180.
<<<
RELATIONS:
- TYPE: Parent
  VALUE: SII-180
  ROLE: Refines

[REQUIREMENT]
UID: C2-SII-190
STATUS: Draft
TAGS: NEEDS_WORKING_GROUP_REVIEW
STATEMENT: >>>
Class 2 devices SHALL satisfy baseline requirement SII-190.
<<<
RELATIONS:
- TYPE: Parent
  VALUE: SII-190
  ROLE: Refines

[REQUIREMENT]
UID: C2-SII-200
STATUS: Draft
TAGS: NEEDS_WORKING_GROUP_REVIEW
STATEMENT: >>>
Class 2 devices SHALL satisfy baseline requirement SII-200.
<<<
RELATIONS:
- TYPE: Parent
  VALUE: SII-200
  ROLE: Refines

[REQUIREMENT]
UID: C2-HW-010
STATUS: Draft
TAGS: NEEDS_WORKING_GROUP_REVIEW
STATEMENT: >>>
Class 2 devices SHALL satisfy baseline requirement HW-010.
<<<
RELATIONS:
- TYPE: Parent
  VALUE: HW-010
  ROLE: Refines

[REQUIREMENT]
UID: C2-RB-010
STATUS: Draft
TAGS: NEEDS_WORKING_GROUP_REVIEW
STATEMENT: >>>
Class 2 devices SHALL satisfy baseline requirement RB-010.
<<<
RELATIONS:
- TYPE: Parent
  VALUE: RB-010
  ROLE: Refines

[REQUIREMENT]
UID: C2-SPL-010
STATUS: Draft
TAGS: NEEDS_WORKING_GROUP_REVIEW
STATEMENT: >>>
Class 2 devices SHALL satisfy baseline requirement SPL-010.
<<<
RELATIONS:
- TYPE: Parent
  VALUE: SPL-010
  ROLE: Refines

[[/SECTION]]

[[SECTION]]
TITLE: Vehicle Bus Connection Security Requirements Applicability

[REQUIREMENT]
UID: C2-VEH-AC-010
STATUS: Draft
TAGS: NEEDS_WORKING_GROUP_REVIEW
STATEMENT: >>>
Class 2 vehicle network interfaces SHALL satisfy requirement VEH-AC-010.
<<<
RELATIONS:
- TYPE: Parent
  VALUE: VEH-AC-010
  ROLE: Refines

[REQUIREMENT]
UID: C2-VEH-AC-020
STATUS: Draft
TAGS: NEEDS_WORKING_GROUP_REVIEW
STATEMENT: >>>
Class 2 vehicle network interfaces SHALL satisfy requirement VEH-AC-020.
<<<
RELATIONS:
- TYPE: Parent
  VALUE: VEH-AC-020
  ROLE: Refines

[REQUIREMENT]
UID: C2-VEH-AC-030
STATUS: Draft
TAGS: NEEDS_WORKING_GROUP_REVIEW
STATEMENT: >>>
Class 2 vehicle network interfaces SHALL satisfy requirement VEH-AC-030.
<<<
RELATIONS:
- TYPE: Parent
  VALUE: VEH-AC-030
  ROLE: Refines

[REQUIREMENT]
UID: C2-VEH-AC-040
STATUS: Draft
TAGS: NEEDS_WORKING_GROUP_REVIEW
STATEMENT: >>>
Class 2 vehicle network interfaces SHALL satisfy requirement VEH-AC-040.
<<<
RELATIONS:
- TYPE: Parent
  VALUE: VEH-AC-040
  ROLE: Refines

[REQUIREMENT]
UID: C2-VEH-AC-041
STATUS: Draft
TAGS: NEEDS_WORKING_GROUP_REVIEW
STATEMENT: >>>
Class 2 vehicle network interfaces SHALL satisfy requirement VEH-AC-041.
<<<
RELATIONS:
- TYPE: Parent
  VALUE: VEH-AC-041
  ROLE: Refines

[REQUIREMENT]
UID: C2-VEH-AC-050
STATUS: Draft
TAGS: NEEDS_WORKING_GROUP_REVIEW
STATEMENT: >>>
Class 2 vehicle network interfaces SHALL satisfy requirement VEH-AC-050.
<<<
RELATIONS:
- TYPE: Parent
  VALUE: VEH-AC-050
  ROLE: Refines

[REQUIREMENT]
UID: C2-VEH-AC-080
STATUS: Draft
TAGS: NEEDS_WORKING_GROUP_REVIEW
STATEMENT: >>>
Class 2 vehicle network interfaces SHALL satisfy requirement VEH-AC-080.
<<<
RELATIONS:
- TYPE: Parent
  VALUE: VEH-AC-080
  ROLE: Refines

[REQUIREMENT]
UID: C2-VEH-CM-010
STATUS: Draft
TAGS: NEEDS_WORKING_GROUP_REVIEW
STATEMENT: >>>
Class 2 vehicle network interfaces SHALL satisfy requirement VEH-CM-010.
<<<
RELATIONS:
- TYPE: Parent
  VALUE: VEH-CM-010
  ROLE: Refines

[REQUIREMENT]
UID: C2-VEH-CM-020
STATUS: Draft
TAGS: NEEDS_WORKING_GROUP_REVIEW
STATEMENT: >>>
Class 2 vehicle network interfaces SHALL satisfy requirement VEH-CM-020.
<<<
RELATIONS:
- TYPE: Parent
  VALUE: VEH-CM-020
  ROLE: Refines

[REQUIREMENT]
UID: C2-VEH-CM-030
STATUS: Draft
TAGS: NEEDS_WORKING_GROUP_REVIEW
STATEMENT: >>>
Class 2 vehicle network interfaces SHALL satisfy requirement VEH-CM-030.
<<<
RELATIONS:
- TYPE: Parent
  VALUE: VEH-CM-030
  ROLE: Refines

[REQUIREMENT]
UID: C2-VEH-CM-040
STATUS: Draft
TAGS: NEEDS_WORKING_GROUP_REVIEW
STATEMENT: >>>
Class 2 vehicle network interfaces SHALL satisfy requirement VEH-CM-040.
<<<
RELATIONS:
- TYPE: Parent
  VALUE: VEH-CM-040
  ROLE: Refines

[REQUIREMENT]
UID: C2-VEH-IA-010
STATUS: Draft
TAGS: NEEDS_WORKING_GROUP_REVIEW
STATEMENT: >>>
Class 2 vehicle network interfaces SHALL satisfy requirement VEH-IA-010.
<<<
RELATIONS:
- TYPE: Parent
  VALUE: VEH-IA-010
  ROLE: Refines

[REQUIREMENT]
UID: C2-VEH-IA-020
STATUS: Draft
TAGS: NEEDS_WORKING_GROUP_REVIEW
STATEMENT: >>>
Class 2 vehicle network interfaces SHALL satisfy requirement VEH-IA-020.
<<<
RELATIONS:
- TYPE: Parent
  VALUE: VEH-IA-020
  ROLE: Refines

[REQUIREMENT]
UID: C2-VEH-IA-030
STATUS: Draft
TAGS: NEEDS_WORKING_GROUP_REVIEW
STATEMENT: >>>
Class 2 vehicle network interfaces SHALL satisfy requirement VEH-IA-030.
<<<
RELATIONS:
- TYPE: Parent
  VALUE: VEH-IA-030
  ROLE: Refines

[REQUIREMENT]
UID: C2-VEH-IR-010
STATUS: Draft
TAGS: NEEDS_WORKING_GROUP_REVIEW
STATEMENT: >>>
Class 2 vehicle network interfaces SHALL satisfy requirement VEH-IR-010.
<<<
RELATIONS:
- TYPE: Parent
  VALUE: VEH-IR-010
  ROLE: Refines

[REQUIREMENT]
UID: C2-VEH-M-010
STATUS: Draft
TAGS: NEEDS_WORKING_GROUP_REVIEW
STATEMENT: >>>
Class 2 vehicle network interfaces SHALL satisfy requirement VEH-M-010.
<<<
RELATIONS:
- TYPE: Parent
  VALUE: VEH-M-010
  ROLE: Refines

[REQUIREMENT]
UID: C2-VEH-M-040
STATUS: Draft
TAGS: NEEDS_WORKING_GROUP_REVIEW
STATEMENT: >>>
Class 2 vehicle network interfaces SHALL satisfy requirement VEH-M-040.
<<<
RELATIONS:
- TYPE: Parent
  VALUE: VEH-M-040
  ROLE: Refines

[REQUIREMENT]
UID: C2-VEH-PS-010
STATUS: Draft
TAGS: NEEDS_WORKING_GROUP_REVIEW
STATEMENT: >>>
Class 2 vehicle network interfaces SHALL satisfy requirement VEH-PS-010.
<<<
RELATIONS:
- TYPE: Parent
  VALUE: VEH-PS-010
  ROLE: Refines

[REQUIREMENT]
UID: C2-VEH-RA-010
STATUS: Draft
TAGS: NEEDS_WORKING_GROUP_REVIEW
STATEMENT: >>>
Class 2 vehicle network interfaces SHALL satisfy requirement VEH-RA-010.
<<<
RELATIONS:
- TYPE: Parent
  VALUE: VEH-RA-010
  ROLE: Refines

[REQUIREMENT]
UID: C2-VEH-RA-020
STATUS: Draft
TAGS: NEEDS_WORKING_GROUP_REVIEW
STATEMENT: >>>
Class 2 vehicle network interfaces SHALL satisfy requirement VEH-RA-020.
<<<
RELATIONS:
- TYPE: Parent
  VALUE: VEH-RA-020
  ROLE: Refines

[REQUIREMENT]
UID: C2-VEH-SAA-010
STATUS: Draft
TAGS: NEEDS_WORKING_GROUP_REVIEW
STATEMENT: >>>
Class 2 vehicle network interfaces SHALL satisfy requirement VEH-SAA-010.
<<<
RELATIONS:
- TYPE: Parent
  VALUE: VEH-SAA-010
  ROLE: Refines

[REQUIREMENT]
UID: C2-VEH-SAA-020
STATUS: Draft
TAGS: NEEDS_WORKING_GROUP_REVIEW
STATEMENT: >>>
Class 2 vehicle network interfaces SHALL satisfy requirement VEH-SAA-020.
<<<
RELATIONS:
- TYPE: Parent
  VALUE: VEH-SAA-020
  ROLE: Refines

[REQUIREMENT]
UID: C2-VEH-SAA-030
STATUS: Draft
TAGS: NEEDS_WORKING_GROUP_REVIEW
STATEMENT: >>>
Class 2 vehicle network interfaces SHALL satisfy requirement VEH-SAA-030.
<<<
RELATIONS:
- TYPE: Parent
  VALUE: VEH-SAA-030
  ROLE: Refines

[REQUIREMENT]
UID: C2-VEH-SAA-040
STATUS: Draft
TAGS: NEEDS_WORKING_GROUP_REVIEW
STATEMENT: >>>
Class 2 vehicle network interfaces SHALL satisfy requirement VEH-SAA-040.
<<<
RELATIONS:
- TYPE: Parent
  VALUE: VEH-SAA-040
  ROLE: Refines

[REQUIREMENT]
UID: C2-VEH-SAA-050
STATUS: Draft
TAGS: NEEDS_WORKING_GROUP_REVIEW
STATEMENT: >>>
Class 2 vehicle network interfaces SHALL satisfy requirement VEH-SAA-050.
<<<
RELATIONS:
- TYPE: Parent
  VALUE: VEH-SAA-050
  ROLE: Refines

[REQUIREMENT]
UID: C2-VEH-SCP-010
STATUS: Draft
TAGS: NEEDS_WORKING_GROUP_REVIEW
STATEMENT: >>>
Class 2 vehicle network interfaces SHALL satisfy requirement VEH-SCP-010.
<<<
RELATIONS:
- TYPE: Parent
  VALUE: VEH-SCP-010
  ROLE: Refines

[REQUIREMENT]
UID: C2-VEH-SCP-011
STATUS: Draft
TAGS: NEEDS_WORKING_GROUP_REVIEW
STATEMENT: >>>
Class 2 vehicle network interfaces SHALL satisfy requirement VEH-SCP-011.
<<<
RELATIONS:
- TYPE: Parent
  VALUE: VEH-SCP-011
  ROLE: Refines

[REQUIREMENT]
UID: C2-VEH-SCP-020
STATUS: Draft
TAGS: NEEDS_WORKING_GROUP_REVIEW
STATEMENT: >>>
Class 2 vehicle network interfaces SHALL satisfy requirement VEH-SCP-020.
<<<
RELATIONS:
- TYPE: Parent
  VALUE: VEH-SCP-020
  ROLE: Refines

[REQUIREMENT]
UID: C2-VEH-SCP-030
STATUS: Draft
TAGS: NEEDS_WORKING_GROUP_REVIEW
STATEMENT: >>>
Class 2 vehicle network interfaces SHALL satisfy requirement VEH-SCP-030.
<<<
RELATIONS:
- TYPE: Parent
  VALUE: VEH-SCP-030
  ROLE: Refines

[REQUIREMENT]
UID: C2-VEH-SCP-040
STATUS: Draft
TAGS: NEEDS_WORKING_GROUP_REVIEW
STATEMENT: >>>
Class 2 vehicle network interfaces SHALL satisfy requirement VEH-SCP-040.
<<<
RELATIONS:
- TYPE: Parent
  VALUE: VEH-SCP-040
  ROLE: Refines

[REQUIREMENT]
UID: C2-VEH-SCP-060
STATUS: Draft
TAGS: NEEDS_WORKING_GROUP_REVIEW
STATEMENT: >>>
Class 2 vehicle network interfaces SHALL satisfy requirement VEH-SCP-060.
<<<
RELATIONS:
- TYPE: Parent
  VALUE: VEH-SCP-060
  ROLE: Refines

[REQUIREMENT]
UID: C2-VEH-SCP-100
STATUS: Draft
TAGS: NEEDS_WORKING_GROUP_REVIEW
STATEMENT: >>>
Class 2 vehicle network interfaces SHALL satisfy requirement VEH-SCP-100.
<<<
RELATIONS:
- TYPE: Parent
  VALUE: VEH-SCP-100
  ROLE: Refines

[REQUIREMENT]
UID: C2-VEH-SCP-140
STATUS: Draft
TAGS: NEEDS_WORKING_GROUP_REVIEW
STATEMENT: >>>
Class 2 vehicle network interfaces SHALL satisfy requirement VEH-SCP-140.
<<<
RELATIONS:
- TYPE: Parent
  VALUE: VEH-SCP-140
  ROLE: Refines

[REQUIREMENT]
UID: C2-VEH-SII-010
STATUS: Draft
TAGS: NEEDS_WORKING_GROUP_REVIEW
STATEMENT: >>>
Class 2 vehicle network interfaces SHALL satisfy requirement VEH-SII-010.
<<<
RELATIONS:
- TYPE: Parent
  VALUE: VEH-SII-010
  ROLE: Refines

[REQUIREMENT]
UID: C2-VEH-SII-011
STATUS: Draft
TAGS: NEEDS_WORKING_GROUP_REVIEW
STATEMENT: >>>
Class 2 vehicle network interfaces SHALL satisfy requirement VEH-SII-011.
<<<
RELATIONS:
- TYPE: Parent
  VALUE: VEH-SII-011
  ROLE: Refines

[REQUIREMENT]
UID: C2-VEH-SII-020
STATUS: Draft
TAGS: NEEDS_WORKING_GROUP_REVIEW
STATEMENT: >>>
Class 2 vehicle network interfaces SHALL satisfy requirement VEH-SII-020.
<<<
RELATIONS:
- TYPE: Parent
  VALUE: VEH-SII-020
  ROLE: Refines

[REQUIREMENT]
UID: C2-VEH-SII-021
STATUS: Draft
TAGS: NEEDS_WORKING_GROUP_REVIEW
STATEMENT: >>>
Class 2 vehicle network interfaces SHALL satisfy requirement VEH-SII-021.
<<<
RELATIONS:
- TYPE: Parent
  VALUE: VEH-SII-021
  ROLE: Refines

[REQUIREMENT]
UID: C2-VEH-SII-030
STATUS: Draft
TAGS: NEEDS_WORKING_GROUP_REVIEW
STATEMENT: >>>
Class 2 vehicle network interfaces SHALL satisfy requirement VEH-SII-030.
<<<
RELATIONS:
- TYPE: Parent
  VALUE: VEH-SII-030
  ROLE: Refines

[REQUIREMENT]
UID: C2-VEH-SII-040
STATUS: Draft
TAGS: NEEDS_WORKING_GROUP_REVIEW
STATEMENT: >>>
Class 2 vehicle network interfaces SHALL satisfy requirement VEH-SII-040.
<<<
RELATIONS:
- TYPE: Parent
  VALUE: VEH-SII-040
  ROLE: Refines

[REQUIREMENT]
UID: C2-VEH-SII-041
STATUS: Draft
TAGS: NEEDS_WORKING_GROUP_REVIEW
STATEMENT: >>>
Class 2 vehicle network interfaces SHALL satisfy requirement VEH-SII-041.
<<<
RELATIONS:
- TYPE: Parent
  VALUE: VEH-SII-041
  ROLE: Refines

[REQUIREMENT]
UID: C2-VEH-SII-060
STATUS: Draft
TAGS: NEEDS_WORKING_GROUP_REVIEW
STATEMENT: >>>
Class 2 vehicle network interfaces SHALL satisfy requirement VEH-SII-060.
<<<
RELATIONS:
- TYPE: Parent
  VALUE: VEH-SII-060
  ROLE: Refines

[REQUIREMENT]
UID: C2-VEH-SII-070
STATUS: Draft
TAGS: NEEDS_WORKING_GROUP_REVIEW
STATEMENT: >>>
Class 2 vehicle network interfaces SHALL satisfy requirement VEH-SII-070.
<<<
RELATIONS:
- TYPE: Parent
  VALUE: VEH-SII-070
  ROLE: Refines

[REQUIREMENT]
UID: C2-VEH-SII-071
STATUS: Draft
TAGS: NEEDS_WORKING_GROUP_REVIEW
STATEMENT: >>>
Class 2 vehicle network interfaces SHALL satisfy requirement VEH-SII-071.
<<<
RELATIONS:
- TYPE: Parent
  VALUE: VEH-SII-071
  ROLE: Refines

[REQUIREMENT]
UID: C2-VEH-SII-080
STATUS: Draft
TAGS: NEEDS_WORKING_GROUP_REVIEW
STATEMENT: >>>
Class 2 vehicle network interfaces SHALL satisfy requirement VEH-SII-080.
<<<
RELATIONS:
- TYPE: Parent
  VALUE: VEH-SII-080
  ROLE: Refines

[REQUIREMENT]
UID: C2-VEH-SII-081
STATUS: Draft
TAGS: NEEDS_WORKING_GROUP_REVIEW
STATEMENT: >>>
Class 2 vehicle network interfaces SHALL satisfy requirement VEH-SII-081.
<<<
RELATIONS:
- TYPE: Parent
  VALUE: VEH-SII-081
  ROLE: Refines

[REQUIREMENT]
UID: C2-VEH-SII-090
STATUS: Draft
TAGS: NEEDS_WORKING_GROUP_REVIEW
STATEMENT: >>>
Class 2 vehicle network interfaces SHALL satisfy requirement VEH-SII-090.
<<<
RELATIONS:
- TYPE: Parent
  VALUE: VEH-SII-090
  ROLE: Refines

[REQUIREMENT]
UID: C2-VEH-SII-120
STATUS: Draft
TAGS: NEEDS_WORKING_GROUP_REVIEW
STATEMENT: >>>
Class 2 vehicle network interfaces SHALL satisfy requirement VEH-SII-120.
<<<
RELATIONS:
- TYPE: Parent
  VALUE: VEH-SII-120
  ROLE: Refines

[REQUIREMENT]
UID: C2-VEH-SII-130
STATUS: Draft
TAGS: NEEDS_WORKING_GROUP_REVIEW
STATEMENT: >>>
Class 2 vehicle network interfaces SHALL satisfy requirement VEH-SII-130.
<<<
RELATIONS:
- TYPE: Parent
  VALUE: VEH-SII-130
  ROLE: Refines

[REQUIREMENT]
UID: C2-VEH-SII-140
STATUS: Draft
TAGS: NEEDS_WORKING_GROUP_REVIEW
STATEMENT: >>>
Class 2 vehicle network interfaces SHALL satisfy requirement VEH-SII-140.
<<<
RELATIONS:
- TYPE: Parent
  VALUE: VEH-SII-140
  ROLE: Refines

[REQUIREMENT]
UID: C2-VEH-SII-150
STATUS: Draft
TAGS: NEEDS_WORKING_GROUP_REVIEW
STATEMENT: >>>
Class 2 vehicle network interfaces SHALL satisfy requirement VEH-SII-150.
<<<
RELATIONS:
- TYPE: Parent
  VALUE: VEH-SII-150
  ROLE: Refines

[REQUIREMENT]
UID: C2-VEH-SII-170
STATUS: Draft
TAGS: NEEDS_WORKING_GROUP_REVIEW
STATEMENT: >>>
Class 2 vehicle network interfaces SHALL satisfy requirement VEH-SII-170.
<<<
RELATIONS:
- TYPE: Parent
  VALUE: VEH-SII-170
  ROLE: Refines

[REQUIREMENT]
UID: C2-VEH-SII-171
STATUS: Draft
TAGS: NEEDS_WORKING_GROUP_REVIEW
STATEMENT: >>>
Class 2 vehicle network interfaces SHALL satisfy requirement VEH-SII-171.
<<<
RELATIONS:
- TYPE: Parent
  VALUE: VEH-SII-171
  ROLE: Refines

[REQUIREMENT]
UID: C2-VEH-SII-180
STATUS: Draft
TAGS: NEEDS_WORKING_GROUP_REVIEW
STATEMENT: >>>
Class 2 vehicle network interfaces SHALL satisfy requirement VEH-SII-180.
<<<
RELATIONS:
- TYPE: Parent
  VALUE: VEH-SII-180
  ROLE: Refines

[REQUIREMENT]
UID: C2-VEH-SII-200
STATUS: Draft
TAGS: NEEDS_WORKING_GROUP_REVIEW
STATEMENT: >>>
Class 2 vehicle network interfaces SHALL satisfy requirement VEH-SII-200.
<<<
RELATIONS:
- TYPE: Parent
  VALUE: VEH-SII-200
  ROLE: Refines

[REQUIREMENT]
UID: C2-VEH-HW-010
STATUS: Draft
TAGS: NEEDS_WORKING_GROUP_REVIEW
STATEMENT: >>>
Class 2 vehicle network interfaces SHALL satisfy requirement VEH-HW-010.
<<<
RELATIONS:
- TYPE: Parent
  VALUE: VEH-HW-010
  ROLE: Refines

[REQUIREMENT]
UID: C2-VEH-RB-010
STATUS: Draft
TAGS: NEEDS_WORKING_GROUP_REVIEW
STATEMENT: >>>
Class 2 vehicle network interfaces SHALL satisfy requirement VEH-RB-010.
<<<
RELATIONS:
- TYPE: Parent
  VALUE: VEH-RB-010
  ROLE: Refines

[REQUIREMENT]
UID: C2-VEH-SPL-010
STATUS: Draft
TAGS: NEEDS_WORKING_GROUP_REVIEW
STATEMENT: >>>
Class 2 vehicle network interfaces SHALL satisfy requirement VEH-SPL-010.
<<<
RELATIONS:
- TYPE: Parent
  VALUE: VEH-SPL-010
  ROLE: Refines

[[/SECTION]]

[[SECTION]]
TITLE: Gateway Security Controls Applicability

[REQUIREMENT]
UID: C2-AGW-S-000
STATEMENT: >>>
Class 2 gateway devices SHALL satisfy requirement AGW-S-000.
<<<
RELATIONS:
- TYPE: Parent
  VALUE: AGW-S-000
  ROLE: Refines

[REQUIREMENT]
UID: C2-AGW-S-001
STATEMENT: >>>
Class 2 gateway devices SHALL satisfy requirement AGW-S-001.
<<<
RELATIONS:
- TYPE: Parent
  VALUE: AGW-S-001
  ROLE: Refines

[REQUIREMENT]
UID: C2-AGW-S-002
STATEMENT: >>>
Class 2 gateway devices SHALL satisfy requirement AGW-S-002.
<<<
RELATIONS:
- TYPE: Parent
  VALUE: AGW-S-002
  ROLE: Refines

[REQUIREMENT]
UID: C2-AGW-S-003
STATEMENT: >>>
Class 2 gateway devices SHALL satisfy requirement AGW-S-003.
<<<
RELATIONS:
- TYPE: Parent
  VALUE: AGW-S-003
  ROLE: Refines

[REQUIREMENT]
UID: C2-AGW-S-004
STATEMENT: >>>
Class 2 gateway devices SHALL satisfy requirement AGW-S-004.
<<<
RELATIONS:
- TYPE: Parent
  VALUE: AGW-S-004
  ROLE: Refines

[REQUIREMENT]
UID: C2-AGW-S-005
STATEMENT: >>>
Class 2 gateway devices SHALL satisfy requirement AGW-S-005.
<<<
RELATIONS:
- TYPE: Parent
  VALUE: AGW-S-005
  ROLE: Refines

[REQUIREMENT]
UID: C2-AGW-S-006
STATEMENT: >>>
Class 2 gateway devices SHALL satisfy requirement AGW-S-006.
<<<
RELATIONS:
- TYPE: Parent
  VALUE: AGW-S-006
  ROLE: Refines

[REQUIREMENT]
UID: C2-AGW-S-007
STATEMENT: >>>
Class 2 gateway devices SHALL satisfy requirement AGW-S-007.
<<<
RELATIONS:
- TYPE: Parent
  VALUE: AGW-S-007
  ROLE: Refines

[REQUIREMENT]
UID: C2-AGW-S-008
STATEMENT: >>>
Class 2 gateway devices SHALL satisfy requirement AGW-S-008.
<<<
RELATIONS:
- TYPE: Parent
  VALUE: AGW-S-008
  ROLE: Refines

[REQUIREMENT]
UID: C2-AGW-S-009
STATEMENT: >>>
Class 2 gateway devices SHALL satisfy requirement AGW-S-009.
<<<
RELATIONS:
- TYPE: Parent
  VALUE: AGW-S-009
  ROLE: Refines

[REQUIREMENT]
UID: C2-AGW-S-010
STATEMENT: >>>
Class 2 gateway devices SHALL satisfy requirement AGW-S-010.
<<<
RELATIONS:
- TYPE: Parent
  VALUE: AGW-S-010
  ROLE: Refines

[REQUIREMENT]
UID: C2-AGW-S-011
STATEMENT: >>>
Class 2 gateway devices SHALL satisfy requirement AGW-S-011.
<<<
RELATIONS:
- TYPE: Parent
  VALUE: AGW-S-011
  ROLE: Refines

[REQUIREMENT]
UID: C2-CGW-S-001
STATEMENT: >>>
Class 2 gateway devices SHALL satisfy requirement CGW-S-001.
<<<
RELATIONS:
- TYPE: Parent
  VALUE: CGW-S-001
  ROLE: Refines

[REQUIREMENT]
UID: C2-CGW-S-005a
STATEMENT: >>>
Class 2 gateway devices SHALL satisfy requirement CGW-S-005a.
<<<
RELATIONS:
- TYPE: Parent
  VALUE: CGW-S-005a
  ROLE: Refines

[REQUIREMENT]
UID: C2-CGW-S-005b
STATEMENT: >>>
Class 2 gateway devices SHALL satisfy requirement CGW-S-005b.
<<<
RELATIONS:
- TYPE: Parent
  VALUE: CGW-S-005b
  ROLE: Refines

[REQUIREMENT]
UID: C2-CGW-S-005c
STATEMENT: >>>
Class 2 gateway devices SHALL satisfy requirement CGW-S-005c.
<<<
RELATIONS:
- TYPE: Parent
  VALUE: CGW-S-005c
  ROLE: Refines

[REQUIREMENT]
UID: C2-CGW-S-005d
STATEMENT: >>>
Class 2 gateway devices SHALL satisfy requirement CGW-S-005d.
<<<
RELATIONS:
- TYPE: Parent
  VALUE: CGW-S-005d
  ROLE: Refines

[REQUIREMENT]
UID: C2-CGW-S-005e
STATEMENT: >>>
Class 2 gateway devices SHALL satisfy requirement CGW-S-005e.
<<<
RELATIONS:
- TYPE: Parent
  VALUE: CGW-S-005e
  ROLE: Refines

[REQUIREMENT]
UID: C2-CGW-S-006
STATEMENT: >>>
Class 2 gateway devices SHALL satisfy requirement CGW-S-006.
<<<
RELATIONS:
- TYPE: Parent
  VALUE: CGW-S-006
  ROLE: Refines

[REQUIREMENT]
UID: C2-CGW-S-007
STATEMENT: >>>
Class 2 gateway devices SHALL satisfy requirement CGW-S-007.
<<<
RELATIONS:
- TYPE: Parent
  VALUE: CGW-S-007
  ROLE: Refines

[REQUIREMENT]
UID: C2-CGW-S-008a
STATEMENT: >>>
Class 2 gateway devices SHALL satisfy requirement CGW-S-008a.
<<<
RELATIONS:
- TYPE: Parent
  VALUE: CGW-S-008a
  ROLE: Refines

[REQUIREMENT]
UID: C2-CGW-S-008b
STATEMENT: >>>
Class 2 gateway devices SHALL satisfy requirement CGW-S-008b.
<<<
RELATIONS:
- TYPE: Parent
  VALUE: CGW-S-008b
  ROLE: Refines

[REQUIREMENT]
UID: C2-CGW-S-008c
STATEMENT: >>>
Class 2 gateway devices SHALL satisfy requirement CGW-S-008c.
<<<
RELATIONS:
- TYPE: Parent
  VALUE: CGW-S-008c
  ROLE: Refines

[REQUIREMENT]
UID: C2-CGW-S-008d
STATEMENT: >>>
Class 2 gateway devices SHALL satisfy requirement CGW-S-008d.
<<<
RELATIONS:
- TYPE: Parent
  VALUE: CGW-S-008d
  ROLE: Refines

[REQUIREMENT]
UID: C2-CGW-S-008e
STATEMENT: >>>
Class 2 gateway devices SHALL satisfy requirement CGW-S-008e.
<<<
RELATIONS:
- TYPE: Parent
  VALUE: CGW-S-008e
  ROLE: Refines

[REQUIREMENT]
UID: C2-CGW-S-013
STATEMENT: >>>
Class 2 gateway devices SHALL satisfy requirement CGW-S-013.
<<<
RELATIONS:
- TYPE: Parent
  VALUE: CGW-S-013
  ROLE: Refines

[REQUIREMENT]
UID: C2-J1939GW-S-039
STATEMENT: >>>
Class 2 gateway devices SHALL satisfy requirement J1939GW-S-039.
<<<
RELATIONS:
- TYPE: Parent
  VALUE: J1939GW-S-039
  ROLE: Refines

[REQUIREMENT]
UID: C2-J1939GW-S-029
STATEMENT: >>>
Class 2 gateway devices SHALL satisfy requirement J1939GW-S-029.
<<<
RELATIONS:
- TYPE: Parent
  VALUE: J1939GW-S-029
  ROLE: Refines

[REQUIREMENT]
UID: C2-J1939GW-S-089
STATEMENT: >>>
Class 2 gateway devices SHALL satisfy requirement J1939GW-S-089.
<<<
RELATIONS:
- TYPE: Parent
  VALUE: J1939GW-S-089
  ROLE: Refines

[REQUIREMENT]
UID: C2-NGW-S-001
STATEMENT: >>>
Class 2 gateway devices SHALL satisfy requirement NGW-S-001.
<<<
RELATIONS:
- TYPE: Parent
  VALUE: NGW-S-001
  ROLE: Refines

[REQUIREMENT]
UID: C2-NGW-S-002
STATEMENT: >>>
Class 2 gateway devices SHALL satisfy requirement NGW-S-002.
<<<
RELATIONS:
- TYPE: Parent
  VALUE: NGW-S-002
  ROLE: Refines

[REQUIREMENT]
UID: C2-NGW-S-003
STATEMENT: >>>
Class 2 gateway devices SHALL satisfy requirement NGW-S-003.
<<<
RELATIONS:
- TYPE: Parent
  VALUE: NGW-S-003
  ROLE: Refines

[REQUIREMENT]
UID: C2-NGW-S-004
STATEMENT: >>>
Class 2 gateway devices SHALL satisfy requirement NGW-S-004.
<<<
RELATIONS:
- TYPE: Parent
  VALUE: NGW-S-004
  ROLE: Refines

[REQUIREMENT]
UID: C2-NGW-S-005
STATEMENT: >>>
Class 2 gateway devices SHALL satisfy requirement NGW-S-005.
<<<
RELATIONS:
- TYPE: Parent
  VALUE: NGW-S-005
  ROLE: Refines

[[/SECTION]]
